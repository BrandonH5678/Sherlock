# FreeCAD Macro - Butte Hill Site Geometry
# Generated by Sherlock GeospatialAgent
# Date: 2025-12-25T15:49:26.579323
# Project: ButteHill_Bedrock_Characterization
#
# This macro creates parametric geometry for underground shelter design.
# Run in FreeCAD by: Macro -> Macros -> Select this file -> Execute

import FreeCAD as App
import Part
import Draft
from FreeCAD import Vector

# Ensure we have an active document
if App.ActiveDocument is None:
    App.newDocument("ButteHill_Site")

doc = App.ActiveDocument


# ============================================================
# PARAMETERS (from freecad_site_inputs.json)
# ============================================================

# Units
UNITS_LENGTH = "ft"  # ft or m
FT_TO_M = 0.3048  # Conversion factor

# Portal Location (UTM 10N)
portal_x = 0.00  # meters easting
portal_y = 0.00  # meters northing
portal_elev = 500.0  # feet

# Adit Axis
adit_bearing = 0.0  # degrees from north
adit_grade_pct = 2.0  # percent downgrade
adit_length_ft = 10.0

# Adit Cross-Section
adit_excavation_w_ft = 7.0
adit_excavation_h_ft = 8.5
adit_clear_w_ft = 6.0
adit_clear_h_ft = 7.0
adit_set_spacing_ft = 3.0

# Collar
collar_thickness_ft = 1.0
collar_key_into_rock_ft = 2.0

# Bedrock Envelope
bedrock_min_ft = 0.0
bedrock_likely_ft = 0.0
bedrock_max_ft = 0.0


# ============================================================
# TERRAIN CONTEXT (Reference Markers)
# ============================================================

# Create terrain group
terrain_group = doc.addObject("App::DocumentObjectGroup", "Terrain")

# Portal reference point
portal_point = doc.addObject("Part::Sphere", "PortalPoint")
portal_point.Radius = 1.0  # 1m sphere
portal_point.Placement = App.Placement(
    Vector(portal_x, portal_y, portal_elev * FT_TO_M),
    App.Rotation()
)
terrain_group.addObject(portal_point)

# North arrow (10m long)
north_arrow = Draft.makeLine(
    Vector(portal_x, portal_y, portal_elev * FT_TO_M),
    Vector(portal_x, portal_y + 10, portal_elev * FT_TO_M)
)
north_arrow.Label = "North"
terrain_group.addObject(north_arrow)


# ============================================================
# PORTAL CANDIDATES
# ============================================================

portal_group = doc.addObject("App::DocumentObjectGroup", "PortalCandidates")


# PC01
portal_PC01 = doc.addObject("Part::Cylinder", "PC01")
portal_PC01.Radius = 2.0
portal_PC01.Height = 0.5
portal_PC01.Placement = App.Placement(
    Vector(0.00, 0.00, 500.0 * FT_TO_M),
    App.Rotation()
)
portal_PC01.ViewObject.ShapeColor = (0.0, 1.0, 0.0)  # Green
portal_group.addObject(portal_PC01)

# ============================================================
# ADIT GEOMETRY
# ============================================================

import math

adit_group = doc.addObject("App::DocumentObjectGroup", "Adit")

# Calculate adit direction vector
bearing_rad = math.radians(adit_bearing)
grade_rad = math.atan(adit_grade_pct / 100)

# Direction components (bearing is from north, so sin/cos swapped)
dx = math.sin(bearing_rad)
dy = math.cos(bearing_rad)
dz = -math.tan(grade_rad)  # Downgrade is negative Z

# Adit length in meters
adit_length_m = adit_length_ft * FT_TO_M

# End point of adit
adit_end_x = portal_x + dx * adit_length_m
adit_end_y = portal_y + dy * adit_length_m
adit_end_z = portal_elev * FT_TO_M + dz * adit_length_m

# Adit centerline
adit_centerline = Draft.makeLine(
    Vector(portal_x, portal_y, portal_elev * FT_TO_M),
    Vector(adit_end_x, adit_end_y, adit_end_z)
)
adit_centerline.Label = "AditCenterline"
adit_group.addObject(adit_centerline)

# Adit excavation profile (simplified as box)
adit_w_m = adit_excavation_w_ft * FT_TO_M
adit_h_m = adit_excavation_h_ft * FT_TO_M

# Create adit as extruded rectangle
adit_profile = Part.makeBox(adit_w_m, adit_h_m, adit_length_m)
adit_excavation = doc.addObject("Part::Feature", "AditExcavation")
adit_excavation.Shape = adit_profile

# Position and rotate adit
# Rotation: align Z axis with adit direction
adit_excavation.Placement = App.Placement(
    Vector(portal_x - adit_w_m/2, portal_y, portal_elev * FT_TO_M - adit_h_m/2),
    App.Rotation(Vector(0, 1, 0), math.degrees(grade_rad)) * App.Rotation(Vector(0, 0, 1), -adit_bearing)
)
adit_excavation.ViewObject.Transparency = 50
adit_excavation.ViewObject.ShapeColor = (0.6, 0.4, 0.2)  # Brown
adit_group.addObject(adit_excavation)


# ============================================================
# COLLAR (Bedrock Interface)
# ============================================================

collar_group = doc.addObject("App::DocumentObjectGroup", "Collar")

# Collar is at bedrock interface (using likely depth)
collar_station_m = bedrock_likely_ft * FT_TO_M

# Calculate collar position along adit
collar_x = portal_x + dx * collar_station_m
collar_y = portal_y + dy * collar_station_m
collar_z = portal_elev * FT_TO_M + dz * collar_station_m

# Collar thickness
collar_t_m = collar_thickness_ft * FT_TO_M
collar_w_m = (adit_excavation_w_ft + 2) * FT_TO_M  # Wider than excavation
collar_h_m = (adit_excavation_h_ft + 2) * FT_TO_M  # Taller than excavation

collar_box = Part.makeBox(collar_w_m, collar_t_m, collar_h_m)
collar = doc.addObject("Part::Feature", "Collar")
collar.Shape = collar_box
collar.Placement = App.Placement(
    Vector(collar_x - collar_w_m/2, collar_y, collar_z - collar_h_m/2),
    App.Rotation(Vector(0, 0, 1), -adit_bearing)
)
collar.ViewObject.ShapeColor = (0.5, 0.5, 0.5)  # Gray
collar_group.addObject(collar)


# ============================================================
# CHAMBERS
# ============================================================

chamber_group = doc.addObject("App::DocumentObjectGroup", "Chambers")

# Chambers start after collar
chamber_start_m = collar_station_m + collar_thickness_ft * FT_TO_M


# CH1: Decon + staging + mechanical core
CH1_box = Part.makeBox(5.49, 7.32, 2.74)
CH1 = doc.addObject("Part::Feature", "CH1")
CH1.Shape = CH1_box
CH1.Placement = App.Placement(
    Vector(collar_x - 2.74, collar_y + 0.00, collar_z - 1.37),
    App.Rotation(Vector(0, 0, 1), -adit_bearing)
)
CH1.ViewObject.ShapeColor = (0.2, 0.4, 0.8)  # Blue
chamber_group.addObject(CH1)


# ============================================================
# LAYER ORGANIZATION
# ============================================================

# Create layer groups for CAD organization
clay_zone = doc.addObject("App::DocumentObjectGroup", "Layer_ClayZone")
bedrock_zone = doc.addObject("App::DocumentObjectGroup", "Layer_BedrockZone")
structures = doc.addObject("App::DocumentObjectGroup", "Layer_Structures")

# Add objects to appropriate layers
clay_zone.addObject(adit_group)
bedrock_zone.addObject(collar_group)
bedrock_zone.addObject(chamber_group)
structures.addObject(terrain_group)
structures.addObject(portal_group)


# Recompute and refresh
doc.recompute()
App.ActiveDocument.recompute()

# Set view to fit all
try:
    import FreeCADGui as Gui
    Gui.ActiveDocument.activeView().viewIsometric()
    Gui.SendMsgToActiveView("ViewFit")
except:
    pass  # GUI may not be available in headless mode

print("Site geometry created successfully!")
print(f"Portal location: {portal_x:.1f}m E, {portal_y:.1f}m N at {portal_elev:.1f}ft elevation")
print(f"Adit length: {adit_length_ft:.1f}ft at {adit_bearing:.1f}° bearing, {adit_grade_pct:.1f}% grade")
